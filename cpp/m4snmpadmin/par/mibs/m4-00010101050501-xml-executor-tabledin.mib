META4-XML-EXECUTOR-TABLEDIN-MIB DEFINITIONS ::= BEGIN

IMPORTS
	OBJECT-GROUP
		FROM SNMPv2-CONF

	DisplayString
		FROM SNMPv2-TC

	MODULE-IDENTITY, OBJECT-IDENTITY, OBJECT-TYPE, Integer32, Unsigned32
		FROM SNMPv2-SMI

	meta4XmlSubsystemModule, xmlSubsystem, xmlSubsystemGroup
		FROM META4-XML-SUBSYSTEM-MIB;


meta4XmlExecutorModule MODULE-IDENTITY
	LAST-UPDATED "200405141200Z"
	ORGANIZATION "Meta4 Spain S.A."
	CONTACT-INFO
		"Meta4 Spain S.A.
		Postal:	Centro Europa Empresarial
			c/ Rozabella, 8
			28230 Las Rozas
			Madrid
			Spain
		Tel.:	(+34) 91 634 85 00
		Fax:	(+34) 91 634 86 86
		Email:	pedrojam@meta4.com
		Web:	www.meta4.com"

	DESCRIPTION
		"This module defines the Xml Executor Table (Dynamic table)."

	REVISION "200405141200Z"
	DESCRIPTION
		"Initial version."
	::= { meta4XmlSubsystemModule 1 }


-- Incluiremos los campos de la tabla.
--
--

xmlExecutorGroup OBJECT-GROUP
	OBJECTS {
		name,
		type,
		startDate,
		serviceId,
		userName,
		sessionId,
		executionBeginDate,
		executionEndDate,
		methodDescription,
		executionState,
		actionCancelExec,
		executionCount,
		errorExecutionCount,
		timeoutExecutionCount,
		userAbortedExecutionCount,
		adminAbortedExecutionCount,
		successfulExecutionCount,
		tps5Sec,
		tps30Sec,
		tps5Min,
		avgExecutionTime5Sec,
		avgExecutionTime30Sec,
		avgExecutionTime5Min,
		avgSSUse5Sec,
		avgSSUse30Sec,
		avgSSUse5Min,
		avgWaitTime5Sec,
		avgWaitTime30Sec,
		avgWaitTime5Min
	}
	STATUS current
	DESCRIPTION
        "-"
    ::= { xmlSubsystemGroup 1 }


-- Definimos la tabla como una secuencia de entradas (registros).
-- La tabla consta de una serie de columnas (propiedades y estadisticas). Tiene una columna obligatoria que es el indice.

xmlExecutorTable OBJECT-TYPE
	SYNTAX SEQUENCE OF XmlExecutorEntry
	MAX-ACCESS not-accessible
	STATUS current
	DESCRIPTION
		"-"
	::= { xmlSubsystem 1001 }

-- La definicion de cada registro: Importante la nomenclatura de mayúsculas de la inicial!.
-- Un registro se identifica por la información propia del registro y por un indice!.

xmlExecutorEntry OBJECT-TYPE 
	SYNTAX XmlExecutorEntry
	MAX-ACCESS not-accessible
	STATUS current
	DESCRIPTION
		"-"
	INDEX { xmlExecutorIndex }
	::= { xmlExecutorTable 1 }

-- Definimos las columnas del registro. Es la struct que define un registro de la tabla.

XmlExecutorEntry ::= SEQUENCE {
		xmlExecutorIndex Unsigned32,
		name DisplayString,
		type DisplayString,
		startDate DisplayString,
		serviceId DisplayString,
		userName DisplayString,
		sessionId DisplayString,
		executionBeginDate DisplayString,
		executionEndDate DisplayString,
		methodDescription DisplayString,
		executionState Integer32,
		actionCancelExec DisplayString,
		executionCount Integer32,
		errorExecutionCount Integer32,
		timeoutExecutionCount Integer32,
		userAbortedExecutionCount Integer32,
		adminAbortedExecutionCount Integer32,
		successfulExecutionCount Integer32,
		tps5Sec Integer32,
		tps30Sec Integer32,
		tps5Min Integer32,
		avgExecutionTime5Sec Integer32,
		avgExecutionTime30Sec Integer32,
		avgExecutionTime5Min Integer32,
		avgSSUse5Sec Integer32,
		avgSSUse30Sec Integer32,
		avgSSUse5Min Integer32,
		avgWaitTime5Sec Integer32,
		avgWaitTime30Sec Integer32,
		avgWaitTime5Min Integer32
	}

-- El indice el el primer hijo (la primera columna) de un registro (entry).
xmlExecutorIndex OBJECT-TYPE 
	SYNTAX Unsigned32
	MAX-ACCESS not-accessible
	STATUS current
	DESCRIPTION
		"-"
	::= { xmlExecutorEntry 1 }

--
-- Ahora definimos el resto de columnas de la tabla. Importante: se empieza por la segunda columna pq
-- la primera es el índice!.

name OBJECT-TYPE
	SYNTAX DisplayString
	MAX-ACCESS read-only
	STATUS current
	DESCRIPTION
		"-"
	::= { xmlExecutorEntry 2 }

type OBJECT-TYPE
	SYNTAX DisplayString
	MAX-ACCESS read-only
	STATUS current
	DESCRIPTION
		"-"
	::= { xmlExecutorEntry 3 }

startDate OBJECT-TYPE
	SYNTAX DisplayString
	UNITS "GMT"
	MAX-ACCESS read-only
	STATUS current
	DESCRIPTION
		"Start Date"
	::= { xmlExecutorEntry 4 }

serviceId OBJECT-TYPE
	SYNTAX DisplayString
	MAX-ACCESS read-only
	STATUS current
	DESCRIPTION
		"Service ID"
	::= { xmlExecutorEntry 5 }

userName OBJECT-TYPE
	SYNTAX DisplayString
	MAX-ACCESS read-only
	STATUS current
	DESCRIPTION
		"User Name"
	::= { xmlExecutorEntry 6 }


sessionId OBJECT-TYPE
	SYNTAX DisplayString
	MAX-ACCESS read-only
	STATUS current
	DESCRIPTION
		"Session ID"
	::= { xmlExecutorEntry 7 }

executionBeginDate OBJECT-TYPE
	SYNTAX DisplayString
	UNITS "GMT"
	MAX-ACCESS read-only
	STATUS current
	DESCRIPTION
		"Execution Begin Date"
	::= { xmlExecutorEntry 8 }

executionEndDate OBJECT-TYPE
	SYNTAX DisplayString
	UNITS "GMT"
	MAX-ACCESS read-only
	STATUS current
	DESCRIPTION
		"Execution End Date"
	::= { xmlExecutorEntry 9 }

methodDescription  OBJECT-TYPE
	SYNTAX DisplayString
	MAX-ACCESS read-only
	STATUS current
	DESCRIPTION
		"Method Description"
	::= { xmlExecutorEntry 10 }

executionState  OBJECT-TYPE
	SYNTAX Integer32
	MAX-ACCESS read-only
	STATUS current
	DESCRIPTION
		"Execution State"
	::= { xmlExecutorEntry 11 }
	
actionCancelExec  OBJECT-TYPE
	SYNTAX DisplayString
	MAX-ACCESS read-write
	STATUS current
	DESCRIPTION
		"Action Cancel Execution"
	::= { xmlExecutorEntry 12 }

executionCount  OBJECT-TYPE
	SYNTAX Integer32
	MAX-ACCESS read-only
	STATUS current
	DESCRIPTION
		"Execution Count"
	::= { xmlExecutorEntry 501 }

errorExecutionCount  OBJECT-TYPE
	SYNTAX Integer32
	MAX-ACCESS read-only
	STATUS current
	DESCRIPTION
		"Error Execution Count"
	::= { xmlExecutorEntry 502 }

timeoutExecutionCount  OBJECT-TYPE
	SYNTAX Integer32
	MAX-ACCESS read-only
	STATUS current
	DESCRIPTION
		"Timed Out Execution Count"
	::= { xmlExecutorEntry 503 }

userAbortedExecutionCount  OBJECT-TYPE
	SYNTAX Integer32
	MAX-ACCESS read-only
	STATUS current
	DESCRIPTION
		"User Aborted Execution Count"
	::= { xmlExecutorEntry 504 }

adminAbortedExecutionCount  OBJECT-TYPE
	SYNTAX Integer32
	MAX-ACCESS read-only
	STATUS current
	DESCRIPTION
		"Admin. Aborted Execution Count"
	::= { xmlExecutorEntry 505 }

successfulExecutionCount  OBJECT-TYPE
	SYNTAX Integer32
	MAX-ACCESS read-only
	STATUS current
	DESCRIPTION
		"Successful Execution Count"
	::= { xmlExecutorEntry 506 }

tps5Sec  OBJECT-TYPE
	SYNTAX Integer32
	MAX-ACCESS read-only
	STATUS current
	DESCRIPTION
		"TPS - Last 5 Seconds"
	::= { xmlExecutorEntry 507 }

tps30Sec  OBJECT-TYPE
	SYNTAX Integer32
	MAX-ACCESS read-only
	STATUS current
	DESCRIPTION
		"TPS - Last 30 Seconds"
	::= { xmlExecutorEntry 508 }

tps5Min  OBJECT-TYPE
	SYNTAX Integer32
	MAX-ACCESS read-only
	STATUS current
	DESCRIPTION
		"TPS - Last 5 Minutes"
	::= { xmlExecutorEntry 509 }

avgExecutionTime5Sec  OBJECT-TYPE
	SYNTAX Integer32
	MAX-ACCESS read-only
	STATUS current
	DESCRIPTION
		"Average Execution Time - Last 5 Seconds"
	::= { xmlExecutorEntry 510 }

avgExecutionTime30Sec  OBJECT-TYPE
	SYNTAX Integer32
	MAX-ACCESS read-only
	STATUS current
	DESCRIPTION
		"Average Execution Time - Last 30 Seconds"
	::= { xmlExecutorEntry 511 }

avgExecutionTime5Min  OBJECT-TYPE
	SYNTAX Integer32
	MAX-ACCESS read-only
	STATUS current
	DESCRIPTION
		"Average Execution Time - Last 5 Minutes"
	::= { xmlExecutorEntry 512 }

avgSSUse5Sec  OBJECT-TYPE
	SYNTAX Integer32
	UNITS "%"
	MAX-ACCESS read-only
	STATUS current
	DESCRIPTION
		"Average SS Use - Last 5 Seconds"
	::= { xmlExecutorEntry 513 }

avgSSUse30Sec  OBJECT-TYPE
	SYNTAX Integer32
	UNITS "%"
	MAX-ACCESS read-only
	STATUS current
	DESCRIPTION
		"Average SS Use - Last 30 Seconds"
	::= { xmlExecutorEntry 514 }

avgSSUse5Min  OBJECT-TYPE
	SYNTAX Integer32
	UNITS "%"
	MAX-ACCESS read-only
	STATUS current
	DESCRIPTION
		"Average SS Use - Last 5 Minutes"
	::= { xmlExecutorEntry 515 }

avgWaitTime5Sec  OBJECT-TYPE
	SYNTAX Integer32
	MAX-ACCESS read-only
	STATUS current
	DESCRIPTION
		"Average Wait Time - Last 5 Seconds"
	::= { xmlExecutorEntry 516 }

avgWaitTime30Sec  OBJECT-TYPE
	SYNTAX Integer32
	MAX-ACCESS read-only
	STATUS current
	DESCRIPTION
		"Average Wait Time - Last 30 Seconds"
	::= { xmlExecutorEntry 517 }

avgWaitTime5Min  OBJECT-TYPE
	SYNTAX Integer32
	MAX-ACCESS read-only
	STATUS current
	DESCRIPTION
		"Average Wait Time - Last 5 Minutes"
	::= { xmlExecutorEntry 518 }


END
