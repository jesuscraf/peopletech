META4-PROXY-SUBSYSTEM-MIB DEFINITIONS ::= BEGIN

IMPORTS
	OBJECT-GROUP
		FROM SNMPv2-CONF

	DisplayString
		FROM SNMPv2-TC

	MODULE-IDENTITY, OBJECT-IDENTITY, OBJECT-TYPE, Integer32
		FROM SNMPv2-SMI

	meta4ServicesSubsystemModule, servicesSubsystem, servicesSubsystemGroup
		FROM META4-SERVICES-SUBSYSTEM-MIB;

meta4ProxySubsystemModule MODULE-IDENTITY
	LAST-UPDATED "200405141200Z"
	ORGANIZATION "Meta4 Spain S.A."
	CONTACT-INFO
		"Meta4 Spain S.A.
		Postal:	Centro Europa Empresarial
			c/ Rozabella, 8
			28230 Las Rozas
			Madrid
			Spain
		Tel.:	(+34) 91 634 85 00
		Fax:	(+34) 91 634 86 86
		Email:	pedrojam@meta4.com
		Web:	www.meta4.com"

	DESCRIPTION
		"This module defines the Proxy subsystem."

	REVISION "200405141200Z"
	DESCRIPTION
		"Initial version."
	::= { meta4ServicesSubsystemModule 3 }


--
-- 

proxySubsystem OBJECT-IDENTITY
	STATUS current
	DESCRIPTION
		"Proxy Subsystem"
	::= { servicesSubsystem 1003 }

proxySubsystemGroup OBJECT-GROUP
	OBJECTS {
		name,
		type,
		startDate,
		state,
		executionCount,
		errorExecutionCount,
		timeoutExecutionCount,
		userAbortedExecutionCount,
		adminAbortedExecutionCount,
		successfulExecutionCount,
		tps5Sec,
		tps30Sec,
		tps5Min,
		avgExecutionTime5Sec,
		avgExecutionTime30Sec,
		avgExecutionTime5Min,
		avgSSUse5Sec,
		avgSSUse30Sec,
		avgSSUse5Min,
		avgWaitTime5Sec,
		avgWaitTime30Sec,
		avgWaitTime5Min

	}
	STATUS current
	DESCRIPTION
		"Proxy Group properties"
	::= { servicesSubsystemGroup 3 }


--
--

name OBJECT-TYPE
	SYNTAX DisplayString
	MAX-ACCESS read-only
	STATUS current
	DESCRIPTION
		"-"
	::= { proxySubsystem 1 }


type OBJECT-TYPE
	SYNTAX DisplayString
	MAX-ACCESS read-only
	STATUS current
	DESCRIPTION
		"-"
	::= { proxySubsystem 2 }

startDate OBJECT-TYPE
	SYNTAX DisplayString
	UNITS "GMT"
	MAX-ACCESS read-only
	STATUS current
	DESCRIPTION
		"Start Date"
	::= { proxySubsystem 3 }

state OBJECT-TYPE
	SYNTAX DisplayString
	MAX-ACCESS read-only
	STATUS current
	DESCRIPTION
		"Current Status"
	::= { proxySubsystem 4 }


executionCount  OBJECT-TYPE
	SYNTAX Integer32
	MAX-ACCESS read-only
	STATUS current
	DESCRIPTION
		"Execution Count"
	::= { proxySubsystem 501 }

errorExecutionCount  OBJECT-TYPE
	SYNTAX Integer32
	MAX-ACCESS read-only
	STATUS current
	DESCRIPTION
		"Error Execution Count"
	::= { proxySubsystem 502 }

timeoutExecutionCount  OBJECT-TYPE
	SYNTAX Integer32
	MAX-ACCESS read-only
	STATUS current
	DESCRIPTION
		"Timed Out Execution Count"
	::= { proxySubsystem 503 }

userAbortedExecutionCount  OBJECT-TYPE
	SYNTAX Integer32
	MAX-ACCESS read-only
	STATUS current
	DESCRIPTION
		"User Aborted Execution Count"
	::= { proxySubsystem 504 }

adminAbortedExecutionCount  OBJECT-TYPE
	SYNTAX Integer32
	MAX-ACCESS read-only
	STATUS current
	DESCRIPTION
		"Admin. Aborted Execution Count"
	::= { proxySubsystem 505 }

successfulExecutionCount  OBJECT-TYPE
	SYNTAX Integer32
	MAX-ACCESS read-only
	STATUS current
	DESCRIPTION
		"Successful Execution Count"
	::= { proxySubsystem 506 }

tps5Sec  OBJECT-TYPE
	SYNTAX Integer32
	MAX-ACCESS read-only
	STATUS current
	DESCRIPTION
		"TPS - Last 5 Seconds"
	::= { proxySubsystem 507 }

tps30Sec  OBJECT-TYPE
	SYNTAX Integer32
	MAX-ACCESS read-only
	STATUS current
	DESCRIPTION
		"TPS - Last 30 Seconds"
	::= { proxySubsystem 508 }

tps5Min  OBJECT-TYPE
	SYNTAX Integer32
	MAX-ACCESS read-only
	STATUS current
	DESCRIPTION
		"TPS - Last 5 Minutes"
	::= { proxySubsystem 509 }

avgExecutionTime5Sec  OBJECT-TYPE
	SYNTAX Integer32
	MAX-ACCESS read-only
	STATUS current
	DESCRIPTION
		"Average Execution Time - Last 5 Seconds"
	::= { proxySubsystem 510 }

avgExecutionTime30Sec  OBJECT-TYPE
	SYNTAX Integer32
	MAX-ACCESS read-only
	STATUS current
	DESCRIPTION
		"Average Execution Time - Last 30 Seconds"
	::= { proxySubsystem 511 }

avgExecutionTime5Min  OBJECT-TYPE
	SYNTAX Integer32
	MAX-ACCESS read-only
	STATUS current
	DESCRIPTION
		"Average Execution Time - Last 5 Minutes"
	::= { proxySubsystem 512 }

avgSSUse5Sec  OBJECT-TYPE
	SYNTAX Integer32
	UNITS "%"
	MAX-ACCESS read-only
	STATUS current
	DESCRIPTION
		"Average SS Use - Last 5 Seconds"
	::= { proxySubsystem 513 }

avgSSUse30Sec  OBJECT-TYPE
	SYNTAX Integer32
	UNITS "%"
	MAX-ACCESS read-only
	STATUS current
	DESCRIPTION
		"Average SS Use - Last 30 Seconds"
	::= { proxySubsystem 514 }

avgSSUse5Min  OBJECT-TYPE
	SYNTAX Integer32
	UNITS "%"
	MAX-ACCESS read-only
	STATUS current
	DESCRIPTION
		"Average SS Use - Last 5 Minutes"
	::= { proxySubsystem 515 }

avgWaitTime5Sec  OBJECT-TYPE
	SYNTAX Integer32
	MAX-ACCESS read-only
	STATUS current
	DESCRIPTION
		"Average Wait Time - Last 5 Seconds"
	::= { proxySubsystem 516 }

avgWaitTime30Sec  OBJECT-TYPE
	SYNTAX Integer32
	MAX-ACCESS read-only
	STATUS current
	DESCRIPTION
		"Average Wait Time - Last 30 Seconds"
	::= { proxySubsystem 517 }

avgWaitTime5Min  OBJECT-TYPE
	SYNTAX Integer32
	MAX-ACCESS read-only
	STATUS current
	DESCRIPTION
		"Average Wait Time - Last 5 Minutes"
	::= { proxySubsystem 518 }


END
