META4-USERS-SUBSYSTEM-MIB DEFINITIONS ::= BEGIN

IMPORTS
	OBJECT-GROUP
		FROM SNMPv2-CONF

	DisplayString
		FROM SNMPv2-TC

	MODULE-IDENTITY, OBJECT-IDENTITY, OBJECT-TYPE, Integer32
		FROM SNMPv2-SMI

	meta4ServicesSubsystemModule, servicesSubsystem, servicesSubsystemGroup
		FROM META4-SERVICES-SUBSYSTEM-MIB;

meta4UsersSubsystemModule MODULE-IDENTITY
	LAST-UPDATED "200405141200Z"
	ORGANIZATION "Meta4 Spain S.A."
	CONTACT-INFO
		"Meta4 Spain S.A.
		Postal:	Centro Europa Empresarial
			c/ Rozabella, 8
			28230 Las Rozas
			Madrid
			Spain
		Tel.:	(+34) 91 634 85 00
		Fax:	(+34) 91 634 86 86
		Email:	pedrojam@meta4.com
		Web:	www.meta4.com"

	DESCRIPTION
		"This module defines the Users subsystem."

	REVISION "200405141200Z"
	DESCRIPTION
		"Initial version."
	::= { meta4ServicesSubsystemModule 2 }


--
-- 

usersSubsystem OBJECT-IDENTITY
	STATUS current
	DESCRIPTION
		"Users Subsystem"
	::= { servicesSubsystem 1002 }

usersSubsystemGroup OBJECT-GROUP
	OBJECTS {
		name,
		type,
		startDate,
		inactivityTimeout,
		timeoutStatus,
		actionCloseSession,
		currentlyLoggedUsers,
		sessionsEstablishedStartup,
		numCurrentSessions
	}
	STATUS current
	DESCRIPTION
		"Users Group properties"
	::= { servicesSubsystemGroup 2 }


--
--

name OBJECT-TYPE
	SYNTAX DisplayString
	MAX-ACCESS read-only
	STATUS current
	DESCRIPTION
		"-"
	::= { usersSubsystem 1 }


type OBJECT-TYPE
	SYNTAX DisplayString
	MAX-ACCESS read-only
	STATUS current
	DESCRIPTION
		"-"
	::= { usersSubsystem 2 }

startDate OBJECT-TYPE
	SYNTAX DisplayString
	UNITS "GMT"
	MAX-ACCESS read-only
	STATUS current
	DESCRIPTION
		"Start Date"
	::= { usersSubsystem 3 }

inactivityTimeout OBJECT-TYPE
	SYNTAX Integer32
	UNITS "min"
	MAX-ACCESS read-write
	STATUS current
	DESCRIPTION
		"Inactivity Timeout"
	::= { usersSubsystem 4 }
   
timeoutStatus OBJECT-TYPE
	SYNTAX DisplayString
	MAX-ACCESS read-write
	STATUS current
	DESCRIPTION
		"Timeout Status"
	::= { usersSubsystem 5 }
	
actionCloseSession OBJECT-TYPE
	SYNTAX DisplayString
	MAX-ACCESS read-write
	STATUS current
	DESCRIPTION
		"Action Close Session"
	::= { usersSubsystem 6 }

currentlyLoggedUsers OBJECT-TYPE
	SYNTAX Integer32
	MAX-ACCESS read-only
	STATUS current
	DESCRIPTION
		"Currently Logged Users"
	::= { usersSubsystem 501 }

sessionsEstablishedStartup OBJECT-TYPE
	SYNTAX Integer32
	MAX-ACCESS read-only
	STATUS current
	DESCRIPTION
		"Sessions Established since Startup"
	::= { usersSubsystem 502 }

numCurrentSessions OBJECT-TYPE
	SYNTAX Integer32
	MAX-ACCESS read-only
	STATUS current
	DESCRIPTION
		"Number of current sessions"
	::= { usersSubsystem 503 }




END
