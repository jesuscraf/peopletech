META4-METADATA-SUBSYSTEM-MIB DEFINITIONS ::= BEGIN

IMPORTS
	OBJECT-GROUP
		FROM SNMPv2-CONF

	DisplayString
		FROM SNMPv2-TC

	MODULE-IDENTITY, OBJECT-IDENTITY, OBJECT-TYPE, Integer32
		FROM SNMPv2-SMI

	meta4ServicesSubsystemModule, servicesSubsystem, servicesSubsystemGroup
		FROM META4-SERVICES-SUBSYSTEM-MIB;

meta4MetadataSubsystemModule MODULE-IDENTITY
	LAST-UPDATED "200405141200Z"
	ORGANIZATION "Meta4 Spain S.A."
	CONTACT-INFO
		"Meta4 Spain S.A.
		Postal:	Centro Europa Empresarial
			c/ Rozabella, 8
			28230 Las Rozas
			Madrid
			Spain
		Tel.:	(+34) 91 634 85 00
		Fax:	(+34) 91 634 86 86
		Email:	pedrojam@meta4.com
		Web:	www.meta4.com"

	DESCRIPTION
		"This module defines the Metadata subsystem."

	REVISION "200405141200Z"
	DESCRIPTION
		"Initial version."
	::= { meta4ServicesSubsystemModule 1 }


--
-- 

metadataSubsystem OBJECT-IDENTITY
	STATUS current
	DESCRIPTION
		"Metadata Subsystem"
	::= { servicesSubsystem 1001 }

metadataSubsystemGroup OBJECT-GROUP
	OBJECTS {
		name,
		type,
		state,
		serviceId,
		startDate,
		metadataCache,
		securityCache,
		presentationCache,
		repositoryKey,
		upperQueueBoundary,
		minExecutorsService,
		maxExecutorsService,
		criticalService,
		outServiceExecutors,
		exceptionHandling,
		executionCount,
		errorExecutionCount,
		timeoutExecutionCount,
		userAbortedExecutionCount,
		adminAbortedExecutionCount,
		successfulExecutionCount,
		tps5Sec,
		tps30Sec,
		tps5Min,
		avgExecutionTime5Sec,
		avgExecutionTime30Sec,
		avgExecutionTime5Min,
		avgSSUse5Sec,
		avgSSUse30Sec,
		avgSSUse5Min,
		avgWaitTime5Sec,
		avgWaitTime30Sec,
		avgWaitTime5Min
	}
	STATUS current
	DESCRIPTION
		"Metadata Group properties"
	::= { servicesSubsystemGroup 1 }


--
--

name OBJECT-TYPE
	SYNTAX DisplayString
	MAX-ACCESS read-only
	STATUS current
	DESCRIPTION
		"-"
	::= { metadataSubsystem 1 }


type OBJECT-TYPE
	SYNTAX DisplayString
	MAX-ACCESS read-only
	STATUS current
	DESCRIPTION
		"-"
	::= { metadataSubsystem 2 }

state OBJECT-TYPE
	SYNTAX DisplayString
	MAX-ACCESS read-only
	STATUS current
	DESCRIPTION
		"Current Status"
	::= { metadataSubsystem 3 }

serviceId OBJECT-TYPE
	SYNTAX DisplayString
	MAX-ACCESS read-only
	STATUS current
	DESCRIPTION
		"Service ID"
	::= { metadataSubsystem 4 }

startDate OBJECT-TYPE
	SYNTAX DisplayString
	UNITS "GMT"
	MAX-ACCESS read-only
	STATUS current
	DESCRIPTION
		"Start Date"
	::= { metadataSubsystem 5 }

metadataCache OBJECT-TYPE
	SYNTAX DisplayString
	MAX-ACCESS read-only
	STATUS current
	DESCRIPTION
		"Metadata Cache"
	::= { metadataSubsystem 6 }

securityCache OBJECT-TYPE
	SYNTAX DisplayString
	MAX-ACCESS read-only
	STATUS current
	DESCRIPTION
		"Security Cache"
	::= { metadataSubsystem 7 }

presentationCache OBJECT-TYPE
	SYNTAX DisplayString
	MAX-ACCESS read-only
	STATUS current
	DESCRIPTION
		"Presentation Cache"
	::= { metadataSubsystem 8 }

repositoryKey OBJECT-TYPE
	SYNTAX DisplayString
	MAX-ACCESS read-only
	STATUS current
	DESCRIPTION
		"Repository Key"
	::= { metadataSubsystem 9 }

upperQueueBoundary OBJECT-TYPE
	SYNTAX Integer32
	MAX-ACCESS read-only
	STATUS current
	DESCRIPTION
		"Upper Queue Boundary"
	::= { metadataSubsystem 10 }

minExecutorsService OBJECT-TYPE
	SYNTAX Integer32
	MAX-ACCESS read-only
	STATUS current
	DESCRIPTION
		"Min. Number of Executors for the Service"
	::= { metadataSubsystem 11 }

maxExecutorsService OBJECT-TYPE
	SYNTAX Integer32
	MAX-ACCESS read-only
	STATUS current
	DESCRIPTION
		"Max. Number of Executors for the Service"
	::= { metadataSubsystem 12 }

criticalService OBJECT-TYPE
	SYNTAX DisplayString
	MAX-ACCESS read-only
	STATUS current
	DESCRIPTION
		"Critical Service"
	::= { metadataSubsystem 13 }

outServiceExecutors OBJECT-TYPE
	SYNTAX Integer32
	MAX-ACCESS read-only
	STATUS current
	DESCRIPTION
		"Out of Service Executors"
	::= { metadataSubsystem 14 }

exceptionHandling OBJECT-TYPE
	SYNTAX DisplayString
	MAX-ACCESS read-only
	STATUS current
	DESCRIPTION
		"Exception Handling"
	::= { metadataSubsystem 15 }

executionCount OBJECT-TYPE
	SYNTAX Integer32
	MAX-ACCESS read-only
	STATUS current
	DESCRIPTION
		"Execution Count"
	::= { metadataSubsystem 501 }

errorExecutionCount OBJECT-TYPE
	SYNTAX Integer32
	MAX-ACCESS read-only
	STATUS current
	DESCRIPTION
		"Error Execution Count"
	::= { metadataSubsystem 502 }

timeoutExecutionCount OBJECT-TYPE
	SYNTAX Integer32
	MAX-ACCESS read-only
	STATUS current
	DESCRIPTION
		"Timed Out Execution Count"
	::= { metadataSubsystem 503 }

userAbortedExecutionCount OBJECT-TYPE
	SYNTAX Integer32
	MAX-ACCESS read-only
	STATUS current
	DESCRIPTION
		"User Aborted Execution Count"
	::= { metadataSubsystem 504 }

adminAbortedExecutionCount OBJECT-TYPE
	SYNTAX Integer32
	MAX-ACCESS read-only
	STATUS current
	DESCRIPTION
		"Admin. Aborted Execution Count"
	::= { metadataSubsystem 505 }

successfulExecutionCount OBJECT-TYPE
	SYNTAX Integer32
	MAX-ACCESS read-only
	STATUS current
	DESCRIPTION
		"Successful Execution Count"
	::= { metadataSubsystem 506 }

tps5Sec OBJECT-TYPE
	SYNTAX Integer32
	MAX-ACCESS read-only
	STATUS current
	DESCRIPTION
		"TPS - Last 5 Seconds"
	::= { metadataSubsystem 507 }

tps30Sec OBJECT-TYPE
	SYNTAX Integer32
	MAX-ACCESS read-only
	STATUS current
	DESCRIPTION
		"TPS - Last 30 Seconds"
	::= { metadataSubsystem 508 }

tps5Min OBJECT-TYPE
	SYNTAX Integer32
	MAX-ACCESS read-only
	STATUS current
	DESCRIPTION
		"TPS - Last 5 Minutes"
	::= { metadataSubsystem 509 }

avgExecutionTime5Sec OBJECT-TYPE
	SYNTAX Integer32
	MAX-ACCESS read-only
	STATUS current
	DESCRIPTION
		"Average Execution Time - Last 5 Seconds"
	::= { metadataSubsystem 510 }

avgExecutionTime30Sec OBJECT-TYPE
	SYNTAX Integer32
	MAX-ACCESS read-only
	STATUS current
	DESCRIPTION
		"Average Execution Time - Last 30 Seconds"
	::= { metadataSubsystem 511 }

avgExecutionTime5Min OBJECT-TYPE
	SYNTAX Integer32
	MAX-ACCESS read-only
	STATUS current
	DESCRIPTION
		"Average Execution Time - Last 5 Minutes"
	::= { metadataSubsystem 512 }

avgSSUse5Sec OBJECT-TYPE
	SYNTAX Integer32
	UNITS "%"
	MAX-ACCESS read-only
	STATUS current
	DESCRIPTION
		"Average SS Use - Last 5 Seconds"
	::= { metadataSubsystem 513 }

avgSSUse30Sec OBJECT-TYPE
	SYNTAX Integer32
	UNITS "%"
	MAX-ACCESS read-only
	STATUS current
	DESCRIPTION
		"Average SS Use - Last 30 Seconds"
	::= { metadataSubsystem 514 }

avgSSUse5Min OBJECT-TYPE
	SYNTAX Integer32
	UNITS "%"
	MAX-ACCESS read-only
	STATUS current
	DESCRIPTION
		"Average SS Use - Last 5 Minutes"
	::= { metadataSubsystem 515 }

avgWaitTime5Sec OBJECT-TYPE
	SYNTAX Integer32
	MAX-ACCESS read-only
	STATUS current
	DESCRIPTION
		"Average Wait Time - Last 5 Seconds"
	::= { metadataSubsystem 516 }

avgWaitTime30Sec OBJECT-TYPE
	SYNTAX Integer32
	MAX-ACCESS read-only
	STATUS current
	DESCRIPTION
		"Average Wait Time - Last 30 Seconds"
	::= { metadataSubsystem 517 }

avgWaitTime5Min OBJECT-TYPE
	SYNTAX Integer32
	MAX-ACCESS read-only
	STATUS current
	DESCRIPTION
		"Average Wait Time - Last 5 Minutes"
	::= { metadataSubsystem 518 }
   
END
